module commutator {
  namespace "commutator";
  prefix test;

  container subscribers {
    config true;

    list subscriber {
      key number;
      
      leaf number { type string; mandatory true; }
      leaf userName { type string; config false; }
      leaf incomingNumber { type string; mandatory true; }
      leaf state {
        type enumeration {
          enum idle;
          enum busy;
          enum active;
        }
        default "idle";
      }
    }
  }
}
